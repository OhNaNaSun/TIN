Attribute VB_Name = "ThisDrawing"
Attribute VB_Base = "0{7AABBB95-79BE-4C0F-8024-EB6AF271231C}"
Attribute VB_GlobalNameSpace = False
Attribute VB_Creatable = False
Attribute VB_PredeclaredId = True
Attribute VB_Exposed = True
Attribute VB_TemplateDerived = False
Attribute VB_Customizable = True
Dim layer3 As AcadLayer

Public Sub main()
'读文件
UserForm1.CommonDialog1.ShowOpen
Dim fname As String
fname = UserForm1.CommonDialog1.filename
  Dim f As Integer
    f = FreeFile
    Open fname For Input As f
    Dim n As Integer
    Dim k As Integer, i As Integer, j As Integer
    Dim points() As Variant
    Dim x(2) As Double
    Dim s As String
    Input #f, n
    ReDim points(n - 1)
For i = 0 To n - 2
     Input #f, k, x(0), x(1), x(2)
     Input #f, s
     points(i) = x
Next
Input #f, k, x(0), x(1), x(2)
points(i) = x
'新建图层，画点
Dim layer0 As AcadLayer
Set layer0 = ThisDrawing.Layers.Add("point")
ThisDrawing.ActiveLayer = layer0
For i = 0 To n - 1
    ThisDrawing.ModelSpace.AddPoint (points(i))
Next

Dim lines() As Variant '每一条线由哪两个点组成，先小后大
Dim ln As Integer '线的条数0 to ln
Dim triangle() As Variant '每个三角形由哪三个点组成
Dim tt As Integer '三角形个数0 to tt
Dim edge() As Variant '存放边缘点
Dim l As Integer '边缘点的个数

'新建图层画Voronoi
Set layer3 = ThisDrawing.Layers.Add("Voronoi")
layer3.color = acBlue

getlinestris points, n, lines, ln, triangle, tt, edge, l

'新建图层画线
Dim layer1 As AcadLayer
Set layer1 = ThisDrawing.Layers.Add("line")
ThisDrawing.ActiveLayer = layer1
layer1.color = acRed
'For j = 0 To ln
'    ThisDrawing.ModelSpace.AddLine points(lines(j)(0)), points(lines(j)(1))
'Next

'新建图层画面
Dim layer2 As AcadLayer
Set layer2 = ThisDrawing.Layers.Add("face")
ThisDrawing.ActiveLayer = layer2
'For j = 0 To tt
'    ThisDrawing.ModelSpace.Add3DFace points(triangle(j)(0)), points(triangle(j)(1)), points(triangle(j)(2)), points(triangle(j)(2))
'Next

'画GRID
Dim layer4 As AcadLayer
Set layer4 = ThisDrawing.Layers.Add("Grid")
ThisDrawing.ActiveLayer = layer4
'Call drawgrid(points, n)

'画等高线
Dim layer5 As AcadLayer
Set layer5 = ThisDrawing.Layers.Add("Contour")
ThisDrawing.ActiveLayer = layer5
Call drawcontour(points, n, lines, triangle, tt, ln)

End Sub

Private Sub drawvoronoi(points() As Variant, ByVal A As Integer, ByVal B As Integer, ByVal C As Integer, ByVal D As Integer)
    ThisDrawing.ActiveLayer = layer3
    If D <> -1 Then
        Dim O1() As Double, O2() As Double
        O1 = GetCC(points(A), points(B), points(C))
        O2 = GetCC(points(A), points(B), points(D))
        Call ThisDrawing.ModelSpace.AddLine(O1, O2)
    End If
End Sub

Private Sub getlinestris(points() As Variant, n As Integer, lines() As Variant, ln As Integer, triangle() As Variant, tt As Integer, edge() As Variant, l As Integer)
 
Dim A As Integer, B As Integer
Dim distance() As Double
ReDim distance(n - 1, n - 1)
For i = 0 To n - 1
    For j = i + 1 To n - 1
        distance(i, j) = Math.Sqr((points(i)(0) - points(j)(0)) ^ 2 + (points(i)(1) - points(j)(1)) ^ 2)
    Next
Next
Dim min As Double
min = distance(0, 1)
A = 0: B = 1
For i = 0 To n - 2
    For j = i + 1 To n - 1
    If i <> j And distance(i, j) < min Then
        min = distance(i, j)
        A = i: B = j
    End If
    Next
Next
'进行拓展
Dim ps() As Integer
Dim ab As Double, bc As Double, ca As Double
ab = Math.Sqr((points(A)(0) - points(B)(0)) ^ 2 + (points(A)(1) - points(B)(1)) ^ 2)
Dim cos As Double
Dim m As Double
Dim C As Integer
C = 0
bc = Math.Sqr((points(0)(0) - points(B)(0)) ^ 2 + (points(0)(1) - points(B)(1)) ^ 2)
ca = Math.Sqr((points(A)(0) - points(0)(0)) ^ 2 + (points(A)(1) - points(0)(1)) ^ 2)
m = (ca ^ 2 + bc ^ 2 - ab ^ 2) / (2 * ca * bc)
For i = 0 To n - 1
If i <> A And i <> B Then
    bc = Math.Sqr((points(i)(0) - points(B)(0)) ^ 2 + (points(i)(1) - points(B)(1)) ^ 2)
    ca = Math.Sqr((points(A)(0) - points(i)(0)) ^ 2 + (points(A)(1) - points(i)(1)) ^ 2)
    cos = (ca ^ 2 + bc ^ 2 - ab ^ 2) / (2 * ca * bc)
        If cos < m Then
           m = cos: C = i
        End If
End If
Next
Dim pts() As Integer
Dim p As Integer
ReDim lines(2)
Dim kk() As Integer
ReDim kk(n - 1, n - 1)
lines(0) = Ar(gmin(A, B), gmax(A, B))
lines(1) = Ar(gmin(B, C), gmax(B, C))
lines(2) = Ar(gmin(A, C), gmax(A, C))
kk(gmin(A, B), gmax(A, B)) = 1
kk(gmin(B, C), gmax(B, C)) = 1
kk(gmin(A, C), gmax(A, C)) = 1
ReDim pts(2)
pts(0) = C
pts(1) = A
pts(2) = B
i = 0
ln = 2  '线的条数0 to ln

ReDim triangle(0)
triangle(0) = Array(lines(0)(0), lines(0)(1), pts(0))
tt = 0 '三角形的个数0-tt
l = -1
Dim pold() As Integer
Dim nold As Integer

Do While i <= ln
Debug.Print i
'nold = -1
If kk(lines(i)(0), lines(i)(1)) = 1 Then
    'Do
    p = tri(lines(i)(0), lines(i)(1), pts(i), points, n)
    Call drawvoronoi(points, lines(i)(0), lines(i)(1), pts(i), p)
    If p = -1 Then
        l = l + 2
        ReDim Preserve edge(l)
        edge(l) = lines(i)(0)
        edge(l - 1) = lines(i)(1)
        'Exit Do
    'ElseIf p = -2 Then
    '    Exit Do
    Else
        'nold = nold + 1
        'ReDim Preserve pold(nold)
        'pold(nold) = p
        If kk(gmin(lines(i)(0), p), gmax(lines(i)(0), p)) < 2 And kk(gmin(lines(i)(1), p), gmax(lines(i)(1), p)) < 2 Then
            tt = tt + 1
            ReDim Preserve triangle(tt)
            triangle(tt) = Array(lines(i)(0), lines(i)(1), p)
            kk(lines(i)(0), lines(i)(1)) = kk(lines(i)(0), lines(i)(1)) + 1
        
            If kk(gmin(lines(i)(1), p), gmax(lines(i)(1), p)) = 0 Then
                ln = ln + 1
                ReDim Preserve lines(ln)
                ReDim Preserve pts(ln)
                lines(ln) = Array(gmin(lines(i)(1), p), gmax(lines(i)(1), p))
                pts(ln) = lines(i)(0)
            End If
            kk(gmin(lines(i)(1), p), gmax(lines(i)(1), p)) = kk(gmin(lines(i)(1), p), gmax(lines(i)(1), p)) + 1
            
            If kk(gmin(lines(i)(0), p), gmax(lines(i)(0), p)) = 0 Then
                ln = ln + 1
                ReDim Preserve lines(ln)
                ReDim Preserve pts(ln)
            
                lines(ln) = Array(gmin(p, lines(i)(0)), gmax(p, lines(i)(0)))
                pts(ln) = lines(i)(1)
            End If
            kk(gmin(lines(i)(0), p), gmax(lines(i)(0), p)) = kk(gmin(lines(i)(0), p), gmax(lines(i)(0), p)) + 1
            'Exit Do
        End If
    
    End If
   ' Loop
End If
i = i + 1
Loop
End Sub
Private Sub drawgrid(points() As Variant, n As Integer)
  Dim minx As Double
  Dim miny As Double
  Dim maxx As Double
  Dim maxy As Double
  Dim gn As Integer
  Dim area As Double
  Dim R As Double
  Dim dx As Double
  Dim dy As Double
  minx = points(getminx(points, n))(0)
  maxx = points(getmaxx(points, n))(0) '200
  miny = points(getminy(points, n))(1)
  maxy = points(getmaxy(points, n))(1)
  area = (maxx - minx) * (maxy - miny)
  R = Math.Sqr(10 * area / 50 ^ 2 / 3.14159)
  dx = (maxx - minx) / 50
  dy = (maxy - miny) / 50
  Dim ptx As Double
  Dim pty As Double
  Dim ptz As Double
  Dim m As Integer
  Dim p As Double
  Dim p1 As Double
  Dim zp As Double
  Dim pt() As Variant
  Dim pp As Double
  Dim mindi As Double
  Dim t As Integer
  ReDim pt((50 + 1) ^ 2 - 1)
  For i = 0 To 50
    For j = 0 To 50
        p = 0
        zp = 0
        pp = p
        For ii = 0 To n - 1
            If (points(ii)(0) - (minx + i * dx)) ^ 2 + (points(ii)(1) - (miny + j * dy)) ^ 2 < R ^ 2 Then
                p1 = (R - Math.Sqr((points(ii)(0) - (minx + i * dx)) ^ 2 + (points(ii)(1) - (miny + j * dy)) ^ 2)) ^ 2 / ((points(ii)(0) - (minx + i * dx)) ^ 2 + (points(ii)(1) - (miny + j * dy)) ^ 2 + 0.00001)
                p = p + p1
                zp = zp + p1 * points(ii)(2)
            End If
        Next
        
            ptx = minx + i * dx
            pty = miny + j * dy
        If p = pp Then
            mindi = (points(0)(0) - ptx) ^ 2 + (points(0)(1) - pty) ^ 2
            t = 0
            For ii = 0 To n - 1
                If (points(ii)(0) - ptx) ^ 2 + (points(ii)(1) - pty) ^ 2 < mindi Then
                    t = ii
                End If
            Next
          ptz = points(t)(2)
        Else
           ptz = zp / p
        End If
        pt(i * 51 + j) = Arr(ptx, pty, ptz)
     Next
  Next
  For i = 0 To 49
    For j = 0 To 49
            If pt(51 * i + j)(2) <> -1 And pt(51 * (i + 1) + j)(2) <> -1 And pt(51 * i + j + 1)(2) <> -1 Then
                ThisDrawing.ModelSpace.AddLine pt(51 * i + j), pt(51 * (i + 1) + j)
                ThisDrawing.ModelSpace.AddLine pt(51 * i + j), pt(51 * i + j + 1)
            End If
    Next
  Next
  For i = 0 To 49
    If pt(51 * i + 50)(2) <> -1 And pt(51 * (i + 1) + 50)(2) <> -1 Then
        ThisDrawing.ModelSpace.AddLine pt(51 * i + 50), pt(51 * (i + 1) + 50)
    End If
  Next
  
  For j = 0 To 49
    If pt(50 * 51 + j)(2) <> -1 And pt(51 * 50 + j + 1)(2) <> -1 Then
        ThisDrawing.ModelSpace.AddLine pt(51 * 50 + j), pt(51 * 50 + j + 1)
    End If
  Next
End Sub

'画等高线
Private Sub drawcontour(points() As Variant, n As Integer, lines() As Variant, triangle() As Variant, tt As Integer, ln As Integer)

Dim kp As Integer
Dim kkpp As Integer
kp = getminz(points, n)
kkpp = getmaxz(points, n)
Dim higt As Integer
Dim hagt As Integer
higt = Int(points(kp)(2)) + 1
hagt = Int(points(kkpp)(2))
Dim hx As Double
Dim hy As Double
Dim hz As Double
Dim jj As Integer
Dim jjj As Integer
Dim ii As Integer
Dim trij() As Integer
Dim trij2 As Integer
Dim jj1 As Integer
Dim tru As Integer
Dim pps1 As Variant
Dim liwei As String
Dim doi As Integer
Dim maxh As Integer
Dim minh As Integer
Dim mn As Integer
Dim mni As Integer
Dim liness() As Variant
For ii = 0 To n - 1
    If Int(points(ii)(2)) = points(ii)(2) Then
        points(ii)(2) = points(ii)(2) + 0.001
    End If
Next
For ii = higt To hagt
    If (ii - higt) Mod 5 = 0 Then
        liwei = acLnWt030
    Else
        liwei = acLnWt005
    End If
    Dim truee As Integer
    mn = -1
    Do
           mni = mn
    For i = 0 To ln
            truee = 1
            For j = 0 To mn
                If lines(i)(0) = liness(j)(0) And lines(i)(1) = liness(j)(1) Then
                    truee = 0
                    Exit For
                End If
            Next
            If truee = 1 Then
                minh = -1
                maxh = -1
                Call finel(lines, points, ii, liness, minh, maxh, pps1, mn, i)
                If mn <> mni Then
                    Exit For
                End If
            End If
            
    Next
    If i = ln + 1 Then
        Exit Do
    End If
        ReDim trij(0)
        trij(0) = -1
        doi = 0
        Call firgo(triangle, points, minh, maxh, ii, tt, pps1, liwei, trij, doi, liness, mn)
        Call firgo(triangle, points, minh, maxh, ii, tt, pps1, liwei, trij, doi, liness, mn)
    Loop
Next
End Sub
Private Sub finel(lines() As Variant, points() As Variant, ii As Integer, liness() As Variant, minh As Integer, maxh As Integer, pps1 As Variant, mn As Integer, ByVal i As Integer)

Dim hx As Double, hy As Double, hz As Double
If (points(lines(i)(0))(2) - ii) * (points(lines(i)(1))(2) - ii) < 0 Then
        mn = mn + 1
        ReDim Preserve liness(mn)
        minh = lines(i)(0)
        maxh = lines(i)(1)
        liness(mn) = Ar(gmin(minh, maxh), gmax(minh, maxh))
        If points(lines(i)(1))(2) < points(lines(i)(0))(2) Then
            minh = lines(i)(1)
            maxh = lines(i)(0)
        End If
        hx = points(minh)(0) + (ii - points(minh)(2)) / (points(maxh)(2) - points(minh)(2)) * (points(maxh)(0) - points(minh)(0))
        hy = points(minh)(1) + (ii - points(minh)(2)) / (points(maxh)(2) - points(minh)(2)) * (points(maxh)(1) - points(minh)(1))
        hz = ii
        pps1 = Arr(hx, hy, hz)
        
    End If
End Sub
Private Sub firgo(triangle() As Variant, points() As Variant, ByVal minh As Integer, ByVal maxh As Integer, ii As Integer, tt As Integer, ByVal pps1 As Variant, liwei As String, trij() As Integer, doi As Integer, liness() As Variant, mn As Integer)
Dim mar1 As Integer, mar2 As Integer
Dim hx As Double, hy As Double, hz As Double
Dim li As AcadLine
Dim pps2 As Variant

Do
For j = 0 To tt
    tru = 1
    For jj1 = 0 To doi
        If j = trij(jj1) Then
           tru = 0
           Exit For
        End If
    Next
    If tru = 1 Then
        For jj = 0 To 2
            If triangle(j)(jj) = minh Then
                mar1 = jj
                For jjj = 0 To 2
                If jjj <> jj And triangle(j)(jjj) = maxh Then
                    mar2 = jjj
                    doi = doi + 1
                    ReDim Preserve trij(doi)
                    trij(doi) = j
                    Exit For
                End If
                Next
                Exit For
            End If
        Next
        If jjj <= 2 And jj <= 2 Then
            Exit For
        End If
    End If
Next
If j = tt + 1 Then
    Exit Do
End If

'mar1是高程小的，点号minh，mar2是高程大的,点号maxh,
For j = 0 To 2
    If j <> mar1 And j <> mar2 Then
        mn = mn + 1
        ReDim Preserve liness(mn)
        If points(triangle(trij(doi))(j))(2) >= ii Then
        maxh = triangle(trij(doi))(j)
        hx = points(minh)(0) + (ii - points(minh)(2)) / (points(maxh)(2) - points(minh)(2)) * (points(maxh)(0) - points(minh)(0))
        hy = points(minh)(1) + (ii - points(minh)(2)) / (points(maxh)(2) - points(minh)(2)) * (points(maxh)(1) - points(minh)(1))
        hz = ii
        ElseIf points(triangle(trij(doi))(j))(2) < ii Then
        minh = triangle(trij(doi))(j)
        hx = points(minh)(0) + (ii - points(minh)(2)) / (points(maxh)(2) - points(minh)(2)) * (points(maxh)(0) - points(minh)(0))
        hy = points(minh)(1) + (ii - points(minh)(2)) / (points(maxh)(2) - points(minh)(2)) * (points(maxh)(1) - points(minh)(1))
        hz = ii
        End If
        liness(mn) = Ar(gmin(minh, maxh), gmax(minh, maxh))
        pps2 = Arr(hx, hy, hz)
    Exit For
    End If
Next
Set li = ThisDrawing.ModelSpace.AddLine(pps1, pps2)
li.Lineweight = liwei
pps1 = pps2
Loop
End Sub
Private Function Arr(hx As Double, hy As Double, hz As Double) As Double()
    Dim tmp(2) As Double
    tmp(0) = hx
    tmp(1) = hy
    tmp(2) = hz
    Arr = tmp
End Function
Private Function Ar(p1 As Integer, p2 As Integer) As Integer()
    Dim tmp(1) As Integer
    tmp(0) = p1
    tmp(1) = p2
    Ar = tmp
End Function

Private Function gd(A As Variant, p1 As Variant, p2 As Integer, ByVal i As Integer, points() As Variant)
Dim llk As Double, llb As Double
If points(p1)(0) = points(A)(0) Then
    gd = (points(i)(0) - points(p1)(0)) * (points(p2)(0) - points(p1)(0))
Else
llk = (points(p1)(1) - points(A)(1)) / (points(p1)(0) - points(A)(0))
llb = points(p1)(1) - llk * points(p1)(0)
gd = ((points(i)(0) * llk + llb - points(i)(1)) * (points(p2)(0) * llk + llb - points(p2)(1)))
End If
End Function
Private Function tri(A As Variant, p1 As Variant, p2 As Integer, points() As Variant, n As Integer) As Integer
Dim cos As Double
    ab = Math.Sqr((points(A)(0) - points(p1)(0)) ^ 2 + (points(A)(1) - points(p1)(1)) ^ 2)
    Dim m As Double
    m = 1
    Dim p As Integer
    p = -1
    'Dim tru As Integer
    'tru = 1
     For i = 0 To n - 1
    '    For j = 0 To nold
    '        If i = pold(j) Then
    '            tru = 0
    '            Exit For
    '        End If
    '    Next
    '    If tru = 1 Then
            If i <> A And i <> p1 And i <> p2 Then
                If gd(A, p1, p2, i, points) < 0 Then
                    bc = Math.Sqr((points(i)(0) - points(p1)(0)) ^ 2 + (points(i)(1) - points(p1)(1)) ^ 2)
                    ca = Math.Sqr((points(A)(0) - points(i)(0)) ^ 2 + (points(A)(1) - points(i)(1)) ^ 2)
                    cos = (ca ^ 2 + bc ^ 2 - ab ^ 2) / (2 * ca * bc)
                        If cos <= m Then
                            m = cos
                            p = i
                        End If
                End If
        
            'End If
        End If
    Next
    'If nold <> -1 And p = -1 Then
    '    tri = -2
    'Else
        tri = p
    'End If
End Function
Private Function gmin(A As Variant, B As Variant) As Variant
    If A <= B Then
    gmin = A
    Else
    gmin = B
    End If
End Function
Private Function gmax(A As Variant, B As Variant) As Variant
If A >= B Then
gmax = A
Else
gmax = B
End If
End Function
Private Function getminx(points As Variant, n As Integer) As Integer
    Dim min As Double
    min = points(0)(0)
    For i = 0 To n - 1
        If points(i)(0) < min Then
            getminx = i
            min = points(i)(0)
        End If
    Next
End Function
Private Function getminy(points As Variant, n As Integer) As Integer
    Dim min As Double
    min = points(0)(1)
    For i = 0 To n - 1
        If points(i)(1) < min Then
            getminy = i
            min = points(i)(1)
        End If
    Next
End Function
Private Function getmaxx(points As Variant, n As Integer) As Integer
    Dim max As Double
    max = points(0)(0)
    For i = 0 To n - 1
        If points(i)(0) > max Then
        getmaxx = i
        max = points(i)(0)
        End If
    Next
End Function
Private Function getmaxy(points As Variant, n As Integer) As Integer
    Dim max As Double
    max = points(0)(1)
    For i = 0 To n - 1
        If points(i)(1) > max Then
        getmaxy = i
        max = points(i)(1)
        End If
    Next
End Function
Private Function getminz(points As Variant, n As Integer) As Integer
    Dim min As Double
    min = points(0)(2)
    For i = 0 To n - 1
        If points(i)(2) < min Then
            getminz = i
            min = points(i)(2)
        End If
    Next
End Function
Private Function getmaxz(points As Variant, n As Integer) As Integer
    Dim max As Double
    max = points(0)(2)
    For i = 0 To n - 1
        If points(i)(2) > max Then
        getmaxz = i
        max = points(i)(2)
        End If
    Next
End Function

Private Function GetCC(A As Variant, B As Variant, C As Variant) As Double()
''' A, B, C是三角形的三个顶点
''' A, B, C必须是一个Double类型的一维数组
''' 函数返回值也是一个Double类型的一维数组

    Dim x1 As Double, x2 As Double, x3 As Double
    Dim y1 As Double, y2 As Double, y3 As Double
    Dim z1 As Double, z2 As Double, z3 As Double
    
    x1 = A(0)
    x2 = B(0)
    x3 = C(0)
    y1 = A(1)
    y2 = B(1)
    y3 = C(1)
    z1 = A(2)
    z2 = B(2)
    z3 = C(2)
    
    Dim A1 As Double, B1 As Double, C1 As Double
    Dim A2 As Double, B2 As Double, C2 As Double
    Dim A3 As Double, B3 As Double, C3 As Double
    
    A1 = (y1 - y2) * (z1 - z3) - (y1 - y3) * (z1 - z2)
    B1 = (x1 - x3) * (z1 - z2) - (x1 - x2) * (z1 - z3)
    C1 = (x1 - x2) * (y1 - y3) - (x1 - x3) * (y1 - y2)
    A2 = x1 - x2
    B2 = y1 - y2
    C2 = z1 - z2
    A3 = x1 - x3
    B3 = y1 - y3
    C3 = z1 - z3
    
    Dim matA(2, 2) As Double, matB(2) As Double
    
    matA(0, 0) = A2
    matA(0, 1) = B2
    matA(0, 2) = C2
    matA(1, 0) = A3
    matA(1, 1) = B3
    matA(1, 2) = C3
    matA(2, 0) = A1
    matA(2, 1) = B1
    matA(2, 2) = C1
    
    matB(0) = A2 * (x1 + x2) / 2 + B2 * (y1 + y2) / 2 + C2 * (z1 + z2) / 2
    matB(1) = A3 * (x1 + x3) / 2 + B3 * (y1 + y3) / 2 + C3 * (z1 + z3) / 2
    matB(2) = A1 * x1 + B1 * y1 + C1 * z1
    
    Dim i As Integer, j As Integer, k As Integer, t As Double
    
    For i = 0 To 2
    
        If matA(i, i) = 0 Then
            For j = 0 To 2
                t = matA(i, j)
                matA(i, j) = matA(i + 1, j)
                matA(i + 1, j) = t
            Next j
            t = matB(i)
            matB(i) = matB(i + 1)
            matB(i + 1) = t
        End If
    
        t = matA(i, i)
        For j = 0 To 2
            matA(i, j) = matA(i, j) / t
        Next j
        matB(i) = matB(i) / t
        
        For j = 0 To 2
            If (i <> j) Then
                t = matA(j, i)
                For k = 0 To 2
                    matA(j, k) = matA(j, k) - t * matA(i, k)
                Next k
                matB(j) = matB(j) - t * matB(i)
            End If
        Next j
        
    Next i
    
    GetCC = matB
    
End Function

Attribute VB_Name = "UserForm1"
Attribute VB_Base = "0{409F0DCC-29C9-49AB-85EA-140A176A07E6}{8EECB168-5FB5-4D0D-9D41-08B0ABC35231}"
Attribute VB_GlobalNameSpace = False
Attribute VB_Creatable = False
Attribute VB_PredeclaredId = True
Attribute VB_Exposed = False
Attribute VB_TemplateDerived = False
Attribute VB_Customizable = False
Private Sub CommandButton1_Click()
 CommonDialog1.ShowOpen
End Sub
